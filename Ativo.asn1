Ativo DEFINITIONS AUTOMATIC TAGS ::=
BEGIN

Ativo ::= SEQUENCE {
  id CHOICE {
  nome PrintableString(SIZE(1..16)),
  codigo INTEGER
  },
  oid OBJECT IDENTIFIER,
  valor INTEGER,
  data NumericString(SIZE(8)),
  horario NumericString (SIZE(6))
}
 
END
